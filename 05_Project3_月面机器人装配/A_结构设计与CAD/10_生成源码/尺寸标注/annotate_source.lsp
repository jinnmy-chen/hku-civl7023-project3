; Read-only geometry; annotations in view-aligned text/leader layers.
(defun p3:w (p) (trans p 1 0))
(defun p3:line (a b)
 (entmakex (list '(0 . "LINE") '(8 . "P3_SIZE_NOTES") '(62 . 4) (cons 10 (p3:w a)) (cons 11 (p3:w b)))))
(defun p3:text (p s h / norm ocs dir)
 (setq norm (trans '(0 0 1) 1 0 T) ocs (trans (p3:w p) 0 norm) dir (trans '(1 0 0) 1 norm T))
 (entmakex (list '(0 . "TEXT") '(8 . "P3_SIZE_NOTES") '(62 . 4) (cons 10 ocs) (cons 40 h) (cons 1 s) '(7 . "Standard") (cons 50 (atan (cadr dir) (car dir))) (cons 210 norm))))
(defun p3:arrow (a b h / dx dy len ux uy v tip base p q)
 (setq dx (- (car b) (car a)) dy (- (cadr b) (cadr a)) len (sqrt (+ (* dx dx) (* dy dy))))
 (if (> len 0.0001)
  (progn
   (setq ux (/ dx len) uy (/ dy len) tip b
    base (list (- (car b) (* h ux)) (- (cadr b) (* h uy)) (caddr b))
    p (list (- (car base) (* h 0.25 uy)) (+ (cadr base) (* h 0.25 ux)) (caddr b))
    q (list (+ (car base) (* h 0.25 uy)) (- (cadr base) (* h 0.25 ux)) (caddr b)))
   (entmakex (list '(0 . "3DFACE") '(8 . "P3_SIZE_NOTES") '(62 . 4) (cons 10 (p3:w tip)) (cons 11 (p3:w p)) (cons 12 (p3:w q)) (cons 13 (p3:w q)))))))
(defun p3:note (entry side row / anchor x y knee attach)
 (setq anchor (trans (cadr entry) 0 1)
  y (- (+ (cadr vc) (* vs 0.32)) (* row vs 0.20))
  x (if (= side 0) (+ leftedge (* vs 0.025)) (+ xmax (* vs 0.045)))
  knee (list (if (= side 0) (- xmin (* vs 0.025)) (+ xmax (* vs 0.025))) y 0)
  attach (list (if (= side 0) (+ x (* (- xmin x) 0.88)) x) y 0))
 (p3:text (list x (+ y (* th 0.35)) 0) (car entry) th)
 (p3:line attach knee) (p3:line knee anchor) (p3:arrow knee anchor (* th 0.7)))
(defun c:P3ANNOTATE (/ oldvars oldfollow oldfiledir oldcmdecho before after f ss p lo hi xmin xmax ymin ymax vc vs ar leftedge rightedge th k)
 (setq oldvars (mapcar '(lambda(n)(list n (getvar n))) '("VIEWCTR" "VIEWSIZE" "VIEWDIR" "VIEWTWIST" "TARGET" "UCSORG" "UCSXDIR" "UCSYDIR"))
  oldfollow (getvar "UCSFOLLOW") oldfiledir (getvar "FILEDIA") oldcmdecho (getvar "CMDECHO"))
 (setvar "UCSFOLLOW" 0) (setvar "FILEDIA" 0) (setvar "CMDECHO" 0)
 (command "_.UCS" "_View")
 (command "_.-LAYER" "_Make" "P3_SIZE_NOTES" "_Color" "4" "P3_SIZE_NOTES" "")
 (setq vc (getvar "VIEWCTR") vs (getvar "VIEWSIZE") ar (/ (car (getvar "SCREENSIZE")) (cadr (getvar "SCREENSIZE")))
  leftedge (- (car vc) (* vs ar 0.5)) rightedge (+ (car vc) (* vs ar 0.5))
  xmin 1e20 xmax -1e20)
 (foreach p corners
  (setq p (trans p 0 1) xmin (min xmin (car p)) xmax (max xmax (car p))))
 (setq th (min (/ vs 45.0) (/ (- xmin leftedge (* vs 0.075)) 16.0) (/ (- rightedge xmax (* vs 0.08)) 16.0)))
 (setq th (max th (/ vs 90.0)))
 (setq leftnotes (vl-sort leftnotes '(lambda(a b) (> (cadr (trans (cadr a) 0 1)) (cadr (trans (cadr b) 0 1))))))
 (setq rightnotes (vl-sort rightnotes '(lambda(a b) (> (cadr (trans (cadr a) 0 1)) (cadr (trans (cadr b) 0 1))))))
 (setq k 0) (foreach p leftnotes (p3:note p 0 k) (setq k (1+ k)))
 (setq k 0) (foreach p rightnotes (p3:note p 1 k) (setq k (1+ k)))
 (command "_.UCS" "_Previous")
 (setvar "UCSFOLLOW" oldfollow)
 (setq after (mapcar '(lambda(n)(list n (getvar n))) '("VIEWCTR" "VIEWSIZE" "VIEWDIR" "VIEWTWIST" "TARGET" "UCSORG" "UCSXDIR" "UCSYDIR")))
 (setq f (open auditpath "w"))
 (write-line (strcat "VIEW_UNCHANGED=" (if (equal oldvars after 0.0000001) "TRUE" "FALSE")) f)
 (write-line (strcat "BEFORE=" (vl-princ-to-string oldvars)) f)
 (write-line (strcat "AFTER=" (vl-princ-to-string after)) f)
 (setq ss (ssget "_X" '((0 . "3DSOLID"))))
 (write-line (strcat "3DSOLID_COUNT=" (itoa (sslength ss))) f)
 (setq ss (ssget "_X" '((0 . "TEXT") (8 . "P3_SIZE_NOTES"))))
 (write-line (strcat "SIZE_LABEL_COUNT=" (itoa (sslength ss))) f) (close f)
 (setvar "FILEDIA" oldfiledir) (setvar "CMDECHO" oldcmdecho)
 (setvar "FILEDIA" 0)
 (command "_.SAVEAS" "_2018" savepath)
 (setvar "FILEDIA" oldfiledir)
 (princ "P3_ANNOTATIONS_SAVED") (princ))
