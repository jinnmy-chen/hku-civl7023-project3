; P3-GrooveKey-v2; mm; native ACIS solids, no STL import.
; Parameter edits: modify the values in p3:parameters, rebuild in a new empty drawing.
(defun p3:parameters ()
 (setq L 50.0 W 30.0 H 22.0 SL 38.0 SD 4.0 SZ 10.0 BC 20.0 BH 3.0 BX 4.0 BY 8.0 TX 2.0 TY 6.0 EX 8.0 EY 12.0 IX 6.0 IY 10.0 EH 0.5 SH 3.5))
(defun p3:rect (x y z w h)
 (entmakex (list '(0 . "LWPOLYLINE") '(100 . "AcDbEntity") '(100 . "AcDbPolyline") '(90 . 4) '(70 . 1) (cons 38 z) (cons 10 (list (- x (/ w 2)) (- y (/ h 2)))) (cons 10 (list (+ x (/ w 2)) (- y (/ h 2)))) (cons 10 (list (+ x (/ w 2)) (+ y (/ h 2)))) (cons 10 (list (- x (/ w 2)) (+ y (/ h 2)))))))
(defun p3:box (x y z w d h)
 (command "_.BOX" (list x y z) (list (+ x w) (+ y d) z) h) (entlast))
(defun p3:loft (x z1 w1 h1 z2 w2 h2 / a b)
 (setq a (p3:rect x 0 z1 w1 h1) b (p3:rect x 0 z2 w2 h2))
 (command "_.LOFT" a b "" "_Cross") (entlast))
(defun p3:subtract (a b) (command "_.SUBTRACT" a "" b "") a)
(defun p3:union (a b) (command "_.UNION" a b "") (entlast))
(defun c:P3BUILD (/ body tool boss mouth wall socket x all f)
 (if (ssget "_X") (progn (princ "Use a NEW EMPTY drawing to protect existing work.") (exit)))
 (if (not outdir) (setq outdir (strcat (getvar "DWGPREFIX") "P3_Rebuild_" (itoa (getvar "MILLISECS")))))
 (vl-mkdir outdir)
 (if (not mode) (setq mode "single"))
 (p3:parameters)
 (setvar "CMDECHO" 0) (setvar "FILEDIA" 0) (setvar "OSMODE" 0)
 (setvar "INSUNITS" 4) (setvar "LUNITS" 2) (setvar "LUPREC" 8)
 (setvar "SOLIDHIST" 1) (setvar "SHOWHIST" 0) (setvar "DELOBJ" 1) (setvar "LOFTNORMALS" 0)
 (command "_.UCS" "_World")
 (command "_.-LAYER" "_Make" "P3_V2" "_Color" "30" "P3_V2" "")
 (setq body (p3:box (- (/ L 2)) (- (/ W 2)) 0 L W H))
 (foreach y (list (- (/ W 2)) (- (/ W 2) SD))
  (setq tool (p3:box (- (/ SL 2)) y SZ SL SD (- H SZ)))
  (setq body (p3:subtract body tool)))
 (foreach x (list (- BC) BC)
  (setq boss (p3:loft x H BX BY (+ H BH) TX TY))
  (command "_.UNION" body boss "") (setq body (entlast)))
 (foreach x (list (- BC) BC)
  (setq mouth (p3:loft x 0 EX EY EH IX IY))
  (setq wall (p3:box (- x (/ IX 2)) (- (/ IY 2)) EH IX IY (- SH EH)))
  (command "_.UNION" mouth wall "") (setq socket (entlast))
  (setq body (p3:subtract body socket)))
 (setq all (ssget "_X" '((0 . "3DSOLID"))))
 (command "_.MASSPROP" all "" "_Yes" (strcat outdir "/AutoCAD_single_mass.mpr"))
 (command "_.ACISOUT" all "" (strcat outdir "/P3_V2_mm.sat"))
 (if (= mode "six")
  (progn
   (foreach pose '((240 80 0 0) (290 80 0 0) (340 80 0 0) (240 80 22 0) (290 80 22 0) (340 80 22 0))
    (command "_.COPY" body "" '(0 0 0) (list (nth 0 pose) (nth 1 pose) (nth 2 pose))))
   (entdel body)))
 (if (= mode "octagon")
  (progn
   (foreach pose poses
    (command "_.COPY" body "" '(0 0 0) '(0 0 0)) (setq tool (entlast))
    (command "_.ROTATE" tool "" '(0 0 0) (nth 3 pose))
    (command "_.MOVE" tool "" '(0 0 0) (list (nth 0 pose) (nth 1 pose) (nth 2 pose))))
   (entdel body)))
 (setq all (ssget "_X" '((0 . "3DSOLID"))))
 (setq f (open (strcat outdir "/" mode "_native_count.txt") "w"))
 (write-line (strcat "3DSOLID_COUNT=" (itoa (sslength all))) f) (close f)
 (command "_.AUDIT" "_Yes")
 (command "_.VPOINT" '(1 -1 1)) (command "_.ZOOM" "_Extents")
 (command "_.QSAVE" (strcat outdir "/" mode "_AutoCAD2027.dwg"))
 (setvar "FILEDIA" 1) (setvar "CMDECHO" 1)
 (princ "P3_NATIVE_BUILD_FINISHED") (princ))
